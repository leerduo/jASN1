PEDefinitions {joint-iso-itu-t(2) international-organizations(23) simalliance(143) euicc-profile(1) spec-version(1) version-two(2)}
DEFINITIONS
AUTOMATIC TAGS
EXTENSIBILITY IMPLIED ::=
BEGIN

ServicesList ::= SEQUENCE {

contactless NULL OPTIONAL,


usim NULL OPTIONAL,
isim NULL OPTIONAL,
csim NULL OPTIONAL,


milenage NULL OPTIONAL,
tuak128 NULL OPTIONAL,
cave NULL OPTIONAL,


gba-usim NULL OPTIONAL,
gba-isim NULL OPTIONAL,
mbms NULL OPTIONAL,
eap NULL OPTIONAL,

	javacard NULL OPTIONAL,
	multos NULL OPTIONAL,


multiple-usim NULL OPTIONAL,
multiple-isim NULL OPTIONAL,
multiple-csim NULL OPTIONAL,


tuak256 NULL OPTIONAL

}

END
